module tng-slice-mngr{

  namespace "urn:5gtango:tng-slice-mngr";

  prefix "tng-slice-mngr";

  organization
    "5GTANGO";

  contact
    "ricard.vilalta@cttc.es";

 description
    "Latest update to tng-slice-mngr data model.";

  revision "2018-02-08" {
    description "Update to tng-slice-mngr initial revision.";
    reference "xxxx";
  }

  grouping s_nssai {
    leaf sst {
      mandatory true;
      type int8;
    }
    leaf sd {
      type int8;
    }
  }
  
  grouping license {
    leaf type {
      type string;
    }
  }
  
  grouping network_service {
    leaf ns_id {
      type string;
      description "A unique identifier of the referenced network service within the scope of this NS descriptor.";
    }
    leaf ns_vendor {
      type string;
      description "The vendor id identifies the NS descriptor uniquely across all function descriptors.";
    }
    leaf ns_name {
      type string;
      description "The name of the referenced NS description.";
    }
    leaf ns_version {
      type string;
      description "The version of the referenced NS description.";
    }
    leaf description {
      type string;
      description "A longer description of the network service.";
    }
  }
  
  grouping service_interface_point {
    leaf id {
      type string;
    }
  }
  
  grouping qos {
    description "slice qos";
    leaf qi_value{
      type string;
      description "5qi value identifies slice quality of service from B to G and 1 to 79";
    }
  }
  
  grouping nst {
    leaf descriptor_schema {
      type string;
    }
    leaf vendor {
      type string;
    }
    leaf name {
      type string;
    }    
    leaf version {
      type string;
    } 
    leaf author {
      type string;
    } 
    leaf description {
      type string;
    } 
    leaf logo {
      type string;
    }
    list licenses {
      key type;
      uses license;
    }
    list network_services {
      key ns_id;
      uses network_service;
    }
    list service_interface_points {
      key "id";
      uses service_interface_point;
    }
    container qos {
      uses qos;
    }      
  }
  
  grouping nsi {
    uses s_nssai;

    leaf nst_ref {
      type leafref {
        path "/nst/name";
      } 
    }
    
    
  }
  
  list nst {
    key "name";
    uses nst;
  } 

  list nsi {
    key "sst";
    uses nsi;
  }

}
